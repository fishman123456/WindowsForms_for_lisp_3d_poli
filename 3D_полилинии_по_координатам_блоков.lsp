(defun
	  C:PL100
		 (/ x1 x2 x3)
					;''(setq x1 ''(getint "введите отступ: "))	;сколько отступать
  (vl-load-com)

 (command "_.-layer" "_m" "101-K2" "")			(command "_.3Dpoly" '(	710919.4662	13815.7019	0.0000	)		'(	20422.6312	31150.5828	0.0000	)	"")
(command "_.-layer" "_m" "102-K2" "")			(command "_.3Dpoly" '(	683358.9666	37304.7533	0.0000	)		'(	20422.6312	28350.5828	0.0000	)	"")
(command "_.-layer" "_m" "2-K2"	"")		(command "_.3Dpoly" '(	1432266.4606	43355.3763	0.0000	)		'(	1413997.1165	48805.0438	0.0000	)	"")
(command "_.-layer" "_m" "216-K2" "")			(command "_.3Dpoly" '(	249582.4099	47876.5536	0.0000	)		'(	227669.5131	53046.3916	0.0000	)	"")
(command "_.-layer" "_m" "218-K2" "")			(command "_.3Dpoly" '(	2802240.5634	28524.5059	0.0000	)		'(	2780135.8865	49997.0803	0.0000	)	"")
(command "_.-layer" "_m" "219-K2" "")			(command "_.3Dpoly" '(	244832.2393	39590.2794	0.0000	)		'(	230416.9717	53046.3916	0.0000	)	"")
(command "_.-layer" "_m" "221-K2" "")			(command "_.3Dpoly" '(	1839321.6786	44060.1679	0.0000	)		'(	1802603.7269	13959.2403	0.0000	)	"")
(command "_.-layer" "_m" "222-K2" "")			(command "_.3Dpoly" '(	217732.7199	41876.5536	0.0000	)		'(	878048.1786	44267.8252	0.0000	)	"")
(command "_.-layer" "_m" "223-K2" "")			(command "_.3Dpoly" '(	1828309.8717	51766.3581	0.0000	)		'(	1801364.9804	14925.0422	0.0000	)	"")
(command "_.-layer" "_m" "224-K2" "")			(command "_.3Dpoly" '(	34897.5750	8632.9689	0.0000	)		'(	31999.7522	7869.5947	0.0000	)	"")
(command "_.-layer" "_m" "5-K2"	"")		(command "_.3Dpoly" '(	1677767.3184	100015.4495	0.0000	)		'(	1604324.0530	75547.8951	0.0000	)	"")
(command "_.-layer" "_m" "551-K2" "")			(command "_.3Dpoly" '(	2471372.4587	23567.1020	0.0000	)		'(	1805081.0618	13959.2403	0.0000	)	"")
(command "_.-layer" "_m" "601-K2" "")			(command "_.3Dpoly" '(	2174594.1237	53812.8730	0.0000	)		'(	1797669.3353	13959.2403	0.0000	)	"")
(command "_.-layer" "_m" "701-K2" "")			(command "_.3Dpoly" '(	3259984.6206	71006.6858	0.0000	)		'(	3179993.6033	32572.2435	0.0000	)	"")
(command "_.-layer" "_m" "704-K2" "")			(command "_.3Dpoly" '(	3465132.1942	73042.4974	0.0000	)		'(	3398496.6397	33442.3325	0.0000	)	"")



)
